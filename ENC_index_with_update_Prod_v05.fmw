FME workspace ENC_index_with_update_Prod_v05.fmw

Parameters:
- SourceDataset_POSTGIS = Post_Prod   # Connection
- DestDataset_CSV2 = $(FME_MF_DIR)ENC   # Destination CSV (Comma Separated Value) Folder
- DestDataset_XLSXW = $(FME_MF_DIR)ENC_index_2021.xlsx   # Destination Microsoft Excel File

Readers:
- POSTGIS_1: POSTGIS from $(SourceDataset_POSTGIS)

Writers:
- CSV2_1: CSV2 to $(DestDataset_CSV2)
- XLSXW_1: XLSXW to $(DestDataset_XLSXW)

SQLCreator
    DATASET = PHPD-Prod
    EXPOSED_ATTRIBUTE_LIST = COMMEN,COMPSC,DATSET,EDITION,ISUDAT,MAX_X,MAX_Y,MIN_X,MIN_Y,NAME,NATFLE,PRODUCT_ID,PRODUCT_STATUS,PRODUCTVERSION_ID,RELEASED,SDO_UTIL.TO_WKTGEOMETRY(GEOM),SETISSUEDATEONEXPORT,UPDDAT,USAGE_ID,VERSION
    FORMAT = ORACLE_SPATIAL
    ORACLE_SPATIAL_CREATE_FEATURE_TABLES_FROM_DATA = Yes
    ORACLE_SPATIAL_NAMED_CONNECTION = PHPD-Prod
    ORACLE_SPATIAL_PERSISTENT_CONNECTION = YES
    ORACLE_SPATIAL_QUERY_FEATURE_TYPES_FOR_MERGE_FILTERS = Yes
    ORACLE_SPATIAL_REMOVE_SCHEMA_QUALIFIER = NO
    ORACLE_SPATIAL_SERVER_TYPE = ORACLE8i
    ORACLE_SPATIAL_SHOW_SYSTEM_TABLES = NO
    ORACLE_SPATIAL_USE_UNIFIED_DATE_ATTRS = YES
    SQL_STATEMENT:
      select p.PRODUCT_ID, p.GEOM,
      PRODUCTVERSION_ID,
      USAGE_ID,
      NAME,
      attd.a_value DATSET,
      attn.a_value COMMEN,
      EDITION,
      VERSION,
      PRODUCT_STATUS,
      atte.RELEASED,
      SETISSUEDATEONEXPORT,
      attc.a_value COMPSC,
      atti.a_value ISUDAT,
      attu.a_value UPDDAT,
      attz.a_value NATFLE,
      SDO_GEOM.SDO_MIN_MBR_ORDINATE(p.GEOM, 1) min_x,
      SDO_GEOM.SDO_MIN_MBR_ORDINATE(p.GEOM, 2) min_y,
      SDO_GEOM.SDO_MAX_MBR_ORDINATE(p.GEOM, 1) max_x,
      SDO_GEOM.SDO_MAX_MBR_ORDINATE(p.GEOM, 2) max_y,
      SDO_UTIL.to_WKTGEOMETRY(geom)
      FROM VECTOR_PRODUCT_VIEW p INNER JOIN
      vector_product_usage pu
      ON pu.product_id=p.product_id

      LEFT OUTER JOIN (
      select distinct p.PRODUCT_ID, DBMS_LOB.SUBSTR(att_value, 10) a_value, acronym from VECTOR_PRODUCT_VIEW p,
      TABLE(p_encapi.getproductversionattributes(productversion_id)) a
      WHERE acronym = 'COMPSC'
      ) attc ON attc.product_id = p.PRODUCT_ID

      LEFT OUTER JOIN (
      select distinct p.PRODUCT_ID, DBMS_LOB.SUBSTR(att_value, 10) a_value, acronym from VECTOR_PRODUCT_VIEW p,
      TABLE(p_encapi.getproductversionattributes(productversion_id)) a
      WHERE acronym = 'ISUDAT'
      ) atti ON atti.product_id = p.PRODUCT_ID

      LEFT OUTER JOIN (
      select distinct p.PRODUCT_ID, DBMS_LOB.SUBSTR(att_value, 10) a_value, acronym from VECTOR_PRODUCT_VIEW p,
      TABLE(p_encapi.getproductversionattributes(productversion_id)) a
      WHERE acronym = 'UPDDAT'
      ) attu ON attu.product_id = p.PRODUCT_ID

      LEFT OUTER JOIN (
      select distinct p.PRODUCT_ID, DBMS_LOB.SUBSTR(att_value, 10) a_value, acronym from VECTOR_PRODUCT_VIEW p,
      TABLE(p_encapi.getproductversionattributes(productversion_id)) a
      WHERE acronym = 'COMMEN'
      ) attn ON attn.product_id = p.PRODUCT_ID

      LEFT OUTER JOIN (
      select distinct p.PRODUCT_ID, DBMS_LOB.SUBSTR(att_value, 10) a_value, acronym from VECTOR_PRODUCT_VIEW p,
      TABLE(p_encapi.getproductversionattributes(productversion_id)) a
      WHERE acronym = 'DATSET'
      ) attd ON attd.product_id = p.PRODUCT_ID

      LEFT OUTER JOIN (
      select distinct p.PRODUCT_ID, DBMS_LOB.SUBSTR(att_value, 10) a_value, acronym from VECTOR_PRODUCT_VIEW p,
      TABLE(p_encapi.getproductversionattributes(productversion_id)) a
      WHERE acronym = 'NATFLE'
      ) attz ON attz.product_id = p.PRODUCT_ID

      JOIN (
      select distinct p.PRODUCT_ID, e.RELEASED from VECTOR_PRODUCT_VIEW p,
      ENCINFO e
      WHERE p.PRODUCTVERSION_ID = e.PRODUCTVERSION_ID
      ) atte ON atte.product_id = p.PRODUCT_ID

      WHERE PRODUCT_STATUS = 'Active' --AND p.PRODUCT_ID=596
      order by product_id
    RESULT -> 2DBoxReplacer
    RESULT -> FeatureMerger [SUPPLIER]
    RESULT -> CoordinateExtractor_2
    RESULT -> Inspector_3
CoordinateExtractor_2
    IND = 0
    MODE = Specify Coordinate
    X_ATTR = _x
    Z_DEFAULT = 0
    -> TestFilter_2
TestFilter_2
    DEFAULT_VALUE = <UNFILTERED>
    TEST_LIST = "BOOL_OP,OR,COMPOSITE_TEST,""""""1"""""",TEST_CLAUSE,TEST @Value(_x) < 0",@Value(_x) < 0,"BOOL_OP,OR,COMPOSITE_TEST,""""""1"""""",TEST_CLAUSE,TEST @Value(_x) > 360",@Value(_x) > 360
    @Value(_x) < 0 -> Offsetter_3
    @Value(_x) > 360 -> Offsetter_4
    <UNFILTERED> -> AttributeManager_3
Offsetter_3
    MODE = Cartesian Coordinate
    XOFF = 360
    YOFF = 0
    ZOFF = 0
    OFFSET -> AttributeManager_3
Offsetter_4
    MODE = Cartesian Coordinate
    XOFF = -360
    YOFF = 0
    ZOFF = 0
    OFFSET -> AttributeManager_3
AttributeManager_3
    ATTR_TABLE = RENAME_SET_VALUE DATSET > enc_no
    -> Tester_4
Tester_4
    BOOL_OP = OR
    COMPOSITE_TEST = 1
    TEST_CLAUSE = CASE_INSENSITIVE_TEST @Value(enc_no) = NZ576551
    TEST_MODE = CASE_INSENSITIVE_TEST
    PASSED -> ChangeDetector_2 [REVISED]
2DBoxReplacer
    MAXXVALATTR = @Value(MAX_X)
    MAXYVALATTR = @Value(MAX_Y)
    MINXVALATTR = @Value(MIN_X)
    MINYVALATTR = @Value(MIN_Y)
    BOX -> CoordinateExtractor
CoordinateExtractor
    IND = 0
    MODE = Specify Coordinate
    X_ATTR = _x
    Z_DEFAULT = 0
    -> TestFilter
TestFilter
    DEFAULT_VALUE = <UNFILTERED>
    TEST_LIST = "BOOL_OP,OR,COMPOSITE_TEST,""""""1"""""",TEST_CLAUSE,TEST @Value(_x) < 0",@Value(_x) < 0,"BOOL_OP,OR,COMPOSITE_TEST,""""""1"""""",TEST_CLAUSE,TEST @Value(_x) > 360",@Value(_x) > 360
    @Value(_x) < 0 -> Offsetter
    @Value(_x) > 360 -> Offsetter_2
    <UNFILTERED> -> Tester_2
Offsetter
    MODE = Cartesian Coordinate
    XOFF = 360
    YOFF = 0
    ZOFF = 0
    OFFSET -> Tester_2
Offsetter_2
    MODE = Cartesian Coordinate
    XOFF = -360
    YOFF = 0
    ZOFF = 0
    OFFSET -> Tester_2
Tester_2
    BOOL_OP = OR
    COMPOSITE_TEST = 1
    TEST_CLAUSE = CASE_INSENSITIVE_TEST @Value(DATSET) = NZ576551
    TEST_MODE = CASE_INSENSITIVE_TEST
Inspector_3
enc_index (reader POSTGIS_1)
    attributes: product_id numeric(10,0), version_id numeric(10,0), usage varchar(254), usage_fil numeric(10,0), enc_no varchar(254),PrimaryKey, enc_name varchar(254), edn_no numeric(10,0), edn_date numeric(10,0), upd_no numeric(10,0), upd_date numeric(10,0), comp_scale numeric(10,0), region varchar(254), min_x numeric(23,7), min_y numeric(23,7), max_x numeric(23,7), max_y numeric(23,7)
    -> FeatureMerger [REQUESTOR]
    -> Tester_5
Tester_5
    BOOL_OP = OR
    COMPOSITE_TEST = 1 OR 2 OR 3 OR 4 OR 5 OR 6
    TEST_CLAUSE:
      CASE_INSENSITIVE_TEST @Value(enc_no) = NZ406422
      CASE_INSENSITIVE_TEST @Value(enc_no) = NZ506422
      CASE_INSENSITIVE_TEST @Value(enc_no) = NZ507625
      CASE_INSENSITIVE_TEST @Value(enc_no) = NZ576251
      CASE_INSENSITIVE_TEST @Value(enc_no) = NZ576252
      CASE_INSENSITIVE_TEST @Value(enc_no) = NZ607625
    TEST_MODE = CASE_INSENSITIVE_TEST
    PASSED -> AttributeManager_2
AttributeManager_2
    ATTR_TABLE:
      RENAME_SET_VALUE product_id > PRODUCT_ID
      RENAME_SET_VALUE version_id > PRODUCTVERSION_ID
    -> ChangeDetector_2 [ORIGINAL]
ChangeDetector_2
    BLANK_AND_MISSING_NAMES_TRAITS_DIFFER = No
    CHECK_COORDINATE_SYSTEMS = No
    LENIENT_MATCH = No
    MATCH = FULL
    PREEMPTIVE_ATTRS = PRODUCTVERSION_ID PRODUCT_ID enc_no
    UNCHANGED_OUTPUT = Output Original
    UPDATED_LIST_NAME = UPDATE
    UPDATED -> CoordinateSystemSetter
    INSERTED -> Inspector
CoordinateSystemSetter
    COORDSYS = EPSG:4326
    -> Tester_3
Tester_3
    BOOL_OP = OR
    COMPOSITE_TEST = 1 OR 2 OR 3 OR 4 OR 5 OR 6
    TEST_CLAUSE:
      CASE_INSENSITIVE_TEST @Value(enc_no) = NZ406422
      CASE_INSENSITIVE_TEST @Value(enc_no) = NZ506422
      CASE_INSENSITIVE_TEST @Value(enc_no) = NZ507625
      CASE_INSENSITIVE_TEST @Value(enc_no) = NZ576251
      CASE_INSENSITIVE_TEST @Value(enc_no) = NZ576252
      CASE_INSENSITIVE_TEST @Value(enc_no) = NZ607625
    TEST_MODE = CASE_INSENSITIVE_TEST
Inspector
FeatureMerger
    ATTR_ACCUM_MODE = Merge Supplier
    ATTR_CONFLICT_RES = Use Requestor
    IGNORE_NULLS = No
    JOIN_KEYS = @Value(enc_no) @Value(DATSET) AUTO @Value(product_id) @Value(PRODUCT_ID) AUTO @Value(version_id) @Value(PRODUCTVERSION_ID) AUTO
    MERGE_TYPE = Attributes Only
    PROCESS_DUPS = NO
    REJECT_NULL_MISSING_KEYS = No
    SUPPLIERS_FIRST = No
    MERGED -> AttributeCreator_3
    UNMERGED_REQUESTOR -> AttributeCreator
    UNUSED_SUPPLIER -> AttributeCreator_2
    <REJECTED> -> AttributeCreator_4
AttributeCreator_3
    ATTR_TABLE = SET_TO comment = unchanged
    -> AttributeManager
AttributeCreator
    ATTR_TABLE = SET_TO comment = current
    -> AttributeManager
AttributeCreator_2
    ATTR_TABLE = SET_TO comment = HPD
    -> AttributeManager
AttributeCreator_4
    ATTR_TABLE = SET_TO comment = rejected
    -> AttributeManager
AttributeManager
    ATTR_TABLE:
      RENAME_SET_VALUE PRODUCT_ID > product_id
      RENAME_SET_VALUE PRODUCTVERSION_ID > version_id
      RENAME_SET_VALUE DATSET > enc_no
      RENAME_SET_VALUE NAME > enc_name
      RENAME_SET_VALUE EDITION > edn_no
      RENAME_SET_VALUE UPDDAT > edn_date
      RENAME_SET_VALUE VERSION > upd_no
      RENAME_SET_VALUE ISUDAT > upd_date
      RENAME_SET_VALUE COMPSC > comp_scale
      RENAME_SET_VALUE MIN_X > min_x
      RENAME_SET_VALUE MIN_Y > min_y
      RENAME_SET_VALUE MAX_X > max_x
      RENAME_SET_VALUE MAX_Y > max_y
    -> Sorter
Sorter
    SORT_PARM = enc_no ALPHA ASCENDING product_id NUMERIC ASCENDING version_id NUMERIC ASCENDING
    SORTED -> Tester
Tester
    BOOL_OP = OR
    COMPOSITE_TEST = 1
    TEST_CLAUSE = CASE_INSENSITIVE_TEST @Value(enc_no) = NZ576551
    TEST_MODE = CASE_INSENSITIVE_TEST
    PASSED -> ENC_20210122 (writer CSV2_1)
    PASSED -> DateTimeStamper
    PASSED -> Inspector_2
Inspector_2
ENC_20210122 (writer CSV2_1)
    attributes: product_id string, version_id string, usage string, usage_fil string, enc_no string, enc_name string, edn_no string, edn_date string, upd_no string, upd_date string, comp_scale string, region string, min_x string, min_y string, max_x string, max_y string
DateTimeStamper
    DATETIME_ATTR = _timestamp
    STAMP_TYPE = date
    TIMEZONE = local
    -> ENC_ (writer XLSXW_1)
ENC_ (writer XLSXW_1)
    attributes: comment string(200), product_id number(20), version_id number(20), usage string(254), usage_fil number(20), enc_no string(254), enc_name string(254), edn_no number(20), edn_date number(20), upd_no number(20), upd_date number(20), comp_scale number(20), min_x number(23), min_y number(23), max_x number(23), max_y number(23), USAGE_ID string(200), COMMEN string(200), PRODUCT_STATUS string(200), SETISSUEDATEONEXPORT string(200), SDO_UTIL.TO_WKTGEOMETRY(GEOM) string(200), region string(254), NATFLE string(200), RELEASED string(200), fme_rejection_code string(20), _timestamp string(20)
Note: unsure about this. appeared on 15/11/2018 for the first time.
AttributeCreator_5
    ATTR_TABLE = SET_TO comment = used_supplier
